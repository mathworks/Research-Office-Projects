# SoftGripper_Requirements

## REQ_GRIP_001: The example shall pick each object of the object set from a table into a tray using a four-finger soft pneumatic gripper on a UR5e arm. (Functional)
Objective. The teaching deliverable is the Model-Based Design workflow for a soft gripper; there is no research claim (engineer, 2026-10-22).
- Rationale: Picking objects of different shape and mass without reprogramming is what soft grippers are used for.
- Keywords: draft, objective

## REQ_GRIP_002: Finger model (Functional)
Chapter.
- Keywords: draft, finger

### REQ_GRIP_003: Each finger shall be modelled as a pseudo-rigid-body chain of N_Joint (8) revolute joints, one per chamber, in Simscape Multibody. (Functional)
Zhu's finger has 8 chambers. Each joint carries a linear spring with an equilibrium offset, a damper, a cubic stiffening correction torque, and a gas converter.
- Rationale: One joint per chamber makes the discretization physical, and Multibody gives contact with arbitrary objects.
- Keywords: draft, finger

### REQ_GRIP_004: The finger model shall reproduce the measured end force of Zhu Table 1 (10-60 kPa, 0-90 degrees) with RMS error at most e_FingerRms. (Functional)
Offline identification (fit_zhu_finger_prb.m, cubic spring) reached 0.050 N RMS, 0.127 N max over 29 points, with the gauge force assumed perpendicular to the tip. The Simscape finger must reproduce the table, not just the offline fit. [GATE A 2026-10-23, engineer accepted the proposed value: 0.08 N leaves margin over the offline fit's 0.050 N for Simscape discretization differences.]
- Rationale: The finger is the subject of the example; matching measured hardware is what makes it reusable.
- Keywords: draft, finger, validation, gate-a-closed

### REQ_GRIP_005: When unloaded, the finger shall bend to theta_Free (75, 90, 110 degrees at 40, 50, 60 kPa) within e_FreeBend. (Functional)
75 and 90 degrees are the zero-force angles of Table 1; 110 degrees at 60 kPa is from the abstract. The offline cubic fit gives 81, 94, 104 degrees. [GATE A 2026-10-23, engineer accepted the proposed value: the offline cubic fit is off by 4-6 deg.]
- Rationale: Free bending is the simplest visible check that pressure and stiffness are balanced correctly.
- Keywords: draft, finger, validation, gate-a-closed

### REQ_GRIP_006: The finger chamber volume shall change with bending by D_Joint (1.594 mL/rad) per joint, so that gas and mechanics are coupled in both directions. (Functional)
D_Joint is identified from Table 1; it is the displacement of each Rotational Mechanical Converter (G), and implies about 2.9 mL of chamber growth at full bend. Checked by a sealed-finger test: blocking the finger must change the chamber pressure as the adiabatic law predicts (soft-arm S-08 pattern, which matched within 0.12 percent).
- Rationale: Two-way coupling is how a real soft gripper senses a grasp: a blocked finger stops growing its chamber.
- Keywords: draft, finger, gas

## REQ_GRIP_007: Gripper pneumatics (Functional)
Chapter.
- Keywords: draft, gas

### REQ_GRIP_008: The gripper shall be supplied by one low-range regulator with full scale p_GripFS (0.1 MPa), saturating at p_GripMax (60 kPa), with output accuracy p_GripAcc (2 percent F.S.). (Functional)
Carries REQ_SOFTARM_057. SMC ITV101x: set range 0.005-0.1 MPa, max supply 0.2 MPa, output accuracy +/-2 percent F.S. (+/-2 kPa).
- Rationale: The fingers work at 0-60 kPa; a 0.5 MPa regulator would be too coarse.
- Keywords: draft, gas

### REQ_GRIP_009: The four fingers shall share one regulated manifold. (Functional)
Engineer decision 2026-10-23: one regulator, as in commercial soft grippers.
- Rationale: All fingers close together, as on real grippers.
- Keywords: draft, gas

### REQ_GRIP_010: When commanded from 0 to p_GripMax, the gripper pressure shall reach 95 percent within t_GripFillPred (17.3 ms, computed by params_softgripper_gas) to within e_FillPred. (Functional)
t_GripFillPred is an independent ideal-nozzle prediction from the ITV101x flow rating (about 80 L/min ANR at 0.2 MPa, graph read) and the 42.6 mL total volume. The soft-arm S-07 equivalent matched within 2.4 percent. Finger volume is an estimate, so this also exposes that assumption. [GATE A 2026-10-23, engineer accepted the proposed value: the ITV101x flow figure is a graph read (about +/- 10 percent).] [M1 2026-10-23: the 12.8 ms quoted at M0 used the soft-arm-era 3-finger, 42.6 mL volume. With 4 fingers + manifold + tube the volume is 57.6 mL and the same prediction gives 17.3 ms. The number is now always taken from params_softgripper_gas.]
- Rationale: The regulator and valve set how fast the gripper can close.
- Keywords: draft, gas, validation, gate-a-closed

## REQ_GRIP_011: Grasp behaviour (Functional)
Chapter.
- Keywords: draft, grasp

### REQ_GRIP_012: The gripper shall reproduce the grasp force of Zhu Table 3 (fingertip 0.41-2.13 N, enveloping 0.79-5.8 N over 10-60 kPa) within e_GraspRel. (Functional)
Gripper-level check: four identified fingers acting together, against an independent measurement that was not used in the identification. [GATE A 2026-10-23, engineer accepted the proposed value: independent measurement; Zhu do not state the gripped object, so contact geometry adds uncertainty.] [Phase 2 2026-10-24, engineer decision: the model is valid for 30-60 kPa. Below 30 kPa the fingers do not reach the test ball (dead zone p0 = 13 kPa; 12.5 mm gap at the 60 mm mount radius chosen so the mango fits). The 10 and 20 kPa points of Table 3 are reported as NOT MET, outside the validity range. Fingertip mode depends on the unpublished ball placement; a height sweep reports that sensitivity.]
- Rationale: Shows the finger model scales correctly to the gripper.
- Keywords: draft, grasp, validation, gate-a-closed

### REQ_GRIP_013: For each fruit, the model shall predict the minimum hold pressure, compared with Zhu Table 4 (apple 30, tomato 35, pear 45, mango 60 kPa; cherry tomato 10 kPa fingertip), within e_HoldPress. (Functional)
Task-level check that makes the model trustworthy to a reader: it predicts what pressure each real fruit needed. [GATE A 2026-10-23, engineer accepted the proposed value: Zhu appear to have tested in 5-10 kPa steps, so a finer tolerance is not meaningful.] [Phase 2 2026-10-24, engineer decision: the model is valid for 30-60 kPa. A fruit whose Table 4 pressure is below 30 kPa (cherry tomato, 10 kPa) is outside the validity range; its result is reported, not counted as a model check. The controller commands 30-60 kPa.]
- Rationale: Ties the soft finger model to an outcome a non-specialist understands.
- Keywords: draft, grasp, validation, gate-a-closed

## REQ_GRIP_014: Object set (Functional)
Chapter.
- Keywords: draft, objects

### REQ_GRIP_015: The object set shall be raspberry (4 g), cherry tomato (15.3 g), apple (200.6 g), tomato (282.9 g), pear (389.1 g) and mango (580.3 g), each modelled as a rigid sphere or ellipsoid with the dimensions, contact stiffness and friction of soft-gripper-object-sourcing.md. (Functional)
Masses from Zhu Table 4 and Fig. 18c (raspberry: carries REQ_SOFTARM_058). Several dimensions, stiffnesses and friction values are estimates [EST], marked in the sourcing table and swept. [M3 2026-10-25, engineer decision: the mango is OUT OF THE PICK SET. At the 60 kPa finger rating a grasp formed on it holds only about its own weight (T-I6 capacity ratio about 1.0 in lift and carry, even at 0.5 m/s^2), so any motion exceeds it; Zhu held it at 60 kPa without moving it, which the model agrees with. The README reports it as beyond the rating. Source: docs/specs/algorithms/pick-controller/rationale.md R3c.] [M3 2026-10-25 small fruit, engineer decision: the raspberry and the cherry tomato are OUTSIDE THIS GRIPPER'S RANGE and are not picked. With the 60 mm finger spacing the curling fingers cannot close on a 20-30 mm fruit: from the table they sweep past it (zero contact); hanging from a stem they shove it 33-41 mm up (stem pull 6.6-8.2 N > F_Detach 2.0 N) at every closing speed and placement tried (T-I7, T-I6 stem). The example picks the apple, tomato and pear (about 70-110 mm); the README states the limits with this evidence. Source: rationale.md R8b.]
- Rationale: Different shapes and masses are what show off a soft gripper.
- Keywords: draft, objects

### REQ_GRIP_016: If the contact force on an object exceeds its bruise limit F_Bruise(obj), then the pick shall be counted as failed. (Functional)
Proposed limits (sourcing): raspberry 3.0 N (engineer-set, carries REQ_SOFTARM_059; agent suggested 1.5 N), cherry tomato 2.5 N [EST], apple 40 N, tomato 11 N, pear 40 N [EST], mango 30 N [EST]. To be confirmed at GATE A. [GATE A 2026-10-23, engineer accepted the proposed value: apple and tomato are measured; raspberry 3.0 N is the engineer's own (agent's 1.5 N suggestion not adopted); cherry tomato, pear and mango are estimates (soft-gripper-object-sourcing.md).]
- Rationale: The gripper's softness only matters if squeezing too hard has a consequence.
- Keywords: draft, objects, failure-path, gate-a-closed

### REQ_GRIP_017: While an object is carried, it shall not slip from the gripper by more than s_SlipMax under the transport acceleration a_Transport. (Functional)
Replaces the raspberry-only F_GripMin (REQ_SOFTARM_060) with a criterion valid for every object. Slip is the binding failure found in the berry analysis (friction is unpublished for several objects). [GATE A 2026-10-23, engineer accepted the proposed value: judgement values: noticeable but harmless slip; brisk but normal cobot motion, about 0.2 g.] [GATE D 2026-10-24, engineer decision: the mango is carried at 0.5 m/s^2 instead of a_Transport. At the 60 kPa finger rating it holds 6.85 N in T-I2, which is its load at 2 m/s^2 (no margin); 0.5 m/s^2 gives a 14 percent margin. Source: docs/specs/algorithms/pick-controller/rationale.md R7.] [M3 2026-10-25, engineer decision: the pear is gripped at 60 kPa and lifted and lowered at 1 m/s^2 (carried at a_Transport): at 2 m/s^2 its lift capacity ratio is 1.60, below the 1.66 that held in the closed-loop picks. Source: rationale.md R3c.]
- Rationale: A dropped mango is as much a failure as a crushed raspberry.
- Keywords: draft, objects, failure-path, gate-a-closed

### REQ_GRIP_018: When a pick is commanded, the object shall be in the tray within T_PickMax (15 s), using at most N_Attempts (3) attempts. (Functional)
Carries REQ_SOFTARM_062 (engineer-set 2026-10-22). RoboSoft 2025 allows 3 attempts per item. [M3 2026-10-25, engineer decision: the mango is OUT OF THE PICK SET. At the 60 kPa finger rating a grasp formed on it holds only about its own weight (T-I6 capacity ratio about 1.0 in lift and carry, even at 0.5 m/s^2), so any motion exceeds it; Zhu held it at 60 kPa without moving it, which the model agrees with. The README reports it as beyond the rating. Source: docs/specs/algorithms/pick-controller/rationale.md R3c.] [M3 2026-10-25 small fruit, engineer decision: the raspberry and the cherry tomato are OUTSIDE THIS GRIPPER'S RANGE and are not picked. With the 60 mm finger spacing the curling fingers cannot close on a 20-30 mm fruit: from the table they sweep past it (zero contact); hanging from a stem they shove it 33-41 mm up (stem pull 6.6-8.2 N > F_Detach 2.0 N) at every closing speed and placement tried (T-I7, T-I6 stem). The example picks the apple, tomato and pear (about 70-110 mm); the README states the limits with this evidence. Source: rationale.md R8b.]
- Rationale: A pick that succeeds eventually is not a demonstration of control.
- Keywords: draft, objects

## REQ_GRIP_019: Arm and controller (Functional)
Chapter.
- Keywords: draft, control

### REQ_GRIP_020: The UR5e shall follow its commanded joint trajectory exactly (kinematic arm), and the README shall state this as a limit of validity. (Functional)
Engineer-approved fidelity call: industrial joint servos are far faster and stiffer than the grasp task; the arm is not the subject.
- Rationale: Spends model fidelity where the teaching point is.
- Keywords: draft, control

### REQ_GRIP_021: The controller shall use only qArmMeas, pGripMeas, bendMeas and the object pose estimate objPoseInit. (Functional)
The frozen interface (system spec 7, 2026-10-23). bendMeas comes from the finger bend sensors that Zhu's fingers embed (Flex Sensor 2.2).
- Rationale: Only signals a real cell has may drive the controller.
- Keywords: draft, control

### REQ_GRIP_022: The truth signals fContact, objPose, objState, thetaJoints and pFinger shall not reach the controller. (Functional)
Carries REQ_SOFTARM_067. Checked structurally by tracing the lines into the controller subsystem.
- Rationale: A controller that sees the true contact force would make the bruise limit trivial to meet.
- Keywords: draft, control, failure-path

## REQ_GRIP_023: Off-nominal (Functional)
Chapter.
- Keywords: draft, off-nominal

### REQ_GRIP_024: When the finger-object friction is lowered to mu_Min, the gripper shall still complete the pick of every object within T_PickMax, or the README shall report which objects fail. (Functional)
Friction is unpublished for pear, mango and raspberry; above-1 values for tomato include adhesion at light load. The sweep range is set in the approved M4 test plan. [Test plan approved by the engineer 2026-10-23: mu_Min = 0.5, test T-N1.]
- Rationale: Shows readers where the design margin is.
- Keywords: draft, off-nominal, test-plan-approved

### REQ_GRIP_025: While one finger chamber leaks to atmosphere through a_LeakFault, the gripper shall still hold the object or the README shall report the failure. (Functional)
Carries the idea of REQ_SOFTARM_064 to the gripper. Leak size set in the approved M4 test plan. [Test plan approved by the engineer 2026-10-23: leak orifice 10 percent of the supply valve area, test T-N2.]
- Rationale: Air leaks are the most common real failure of a pneumatic soft gripper.
- Keywords: draft, off-nominal, fault, test-plan-approved

### REQ_GRIP_026: When the regulator supply droops to p_SupplyMin, the gripper shall still reach the hold pressure of the heaviest object, or the README shall report the limit. (Functional)
ITV101x needs supply >= set + 0.1 MPa, so the mango's 60 kPa needs at least 0.16 MPa supply. Droop magnitude set in the M4 test plan. [Test plan approved by the engineer 2026-10-23: 0.16 MPa = the ITV101x minimum supply for a 60 kPa set (set + 0.1 MPa), test T-N3.]
- Rationale: Shared compressed air in a cell varies.
- Keywords: draft, off-nominal, test-plan-approved

### REQ_GRIP_027: Where the stem option is enabled, the raspberry shall be picked from a stem with detach force F_Detach (2.0 N). (Functional)
Optional scenario (engineer, 2026-10-23). Carries REQ_SOFTARM_058/061. [GATE D 2026-10-24, engineer decision: the raspberry is ALWAYS picked from a stem. From the table the fingertips meet 16 mm above its centre at the 60 mm mounting radius and cannot grasp it. The cherry tomato stays a table pick and is reported as marginal. Source: rationale.md R8.] [M3 2026-10-25 small fruit, engineer decision: the raspberry and the cherry tomato are OUTSIDE THIS GRIPPER'S RANGE and are not picked. With the 60 mm finger spacing the curling fingers cannot close on a 20-30 mm fruit: from the table they sweep past it (zero contact); hanging from a stem they shove it 33-41 mm up (stem pull 6.6-8.2 N > F_Detach 2.0 N) at every closing speed and placement tried (T-I7, T-I6 stem). The example picks the apple, tomato and pear (about 70-110 mm); the README states the limits with this evidence. Source: rationale.md R8b.]
- Rationale: Keeps the delicate-harvest case available.
- Keywords: draft, off-nominal, optional

## REQ_GRIP_028: Example deliverables (Functional)
Chapter.
- Keywords: draft, deliverable

### REQ_GRIP_029: The example shall provide a 3D replay of each pick that reads logged results only and changes no simulated value. (Functional)
Carries REQ_SOFTARM_066. Simulation 3D Robot block (UR5e) plus Sim3D actors; optional product Simulink 3D Animation.
- Rationale: A visual that could alter the result would make the result untrustworthy.
- Keywords: draft, deliverable, visualization

### REQ_GRIP_030: The example shall run with MATLAB, Simulink, Simscape, Simscape Multibody, Stateflow and Robotics System Toolbox; Simulink 3D Animation, Requirements Toolbox and Optimization Toolbox shall be optional. (Functional)
Optimization Toolbox is needed only to re-run the finger identification (engineer decision 2026-10-23); the identified values ship in the params file.
- Rationale: Keeps the example runnable by as many readers as possible.
- Keywords: draft, deliverable

### REQ_GRIP_031: One pick shall simulate within T_RunPick wall time. (Functional)
Target set after the first M2 measurement; the architecture proposes 2 min per 15 s pick. [GATE E 2026-10-25, engineer decision: T_RunPick = 35 min wall per pick, just above the measured 1357-1773 s (23-30 min) for 6.7-7.3 s simulated (daessc, RelTol 1e-4, zero-crossing detection off). Result: PASS for the apple, tomato and pear picks. Source: soft-gripper-verification.md.]
- Rationale: Readers must be able to iterate.
- Keywords: draft, deliverable, performance
